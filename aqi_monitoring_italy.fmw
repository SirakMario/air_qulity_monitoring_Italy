FME workspace aqi_monitoring_italy.fmw

Parameters:
- SourceDataset_SHAPEFILE_2 = $(FME_MF_DIR)aqi_stations.shp   # Source Esri Shapefile(s)

Readers:
- SHAPEFILE_3: SHAPEFILE from $(SourceDataset_SHAPEFILE_2) in EPSG:32632

aqi_stations (reader SHAPEFILE_3)
    attributes: lat varchar(254), lon varchar(254), aqi varchar(254)
    -> AttributeManager_2
AttributeManager_2
    ATTR_TABLE:
      REMOVE aqi (varchar(254))
      SET_TO api_url (varchar(92)) = https://api.waqi.info/feed/geo:${lat};${lon}/?token=5848198a671c35b7c4d0d870c69d1f079b3a0656
    -> HTTPCaller_2
HTTPCaller_2
    CLIENT_CERTIFICATE_TYPE = NONE
    CONNECTION_TIMEOUT_LENGTH = 60
    ERROR_ATTR = _error
    FOLLOW_REDIRECTS = FOLLOW_WITH_GET
    HTTP_METHOD = GET
    MAX_HTTP_VERSION = HTTP_2
    MAX_TRANSFERS_IN_PROGRESS = 25
    MINIMUM_ENCRYPTION_LEVEL = OS_DEFAULT
    REDIRECT_AUTH = ORIGINAL_DOMAIN_ONLY
    RESPONSE_TYPE = Attribute
    SPLIT_MULTIPART_DOWNLOADS = NO
    STATUS_CODE_ATTR = _http_status_code
    TARGET_ATTR = _response_body
    TARGET_ATTR_ENCODING = auto-detect
    TARGET_URL = https://api.waqi.info/feed/geo:@Value(lat);@Value(lon)/?token=5848198a671c35b7c4d0d870c69d1f079b3a0656
    TEST_DIALOG_PARAMETERS_FOR_RESPONSE = authConnection;<Unused> authEnabled;false authMethod;<Unused> authPassword;<Unused> authUsername;<Unused> contentType;<Unused> method;GET multipartContentType;<Unused> requestUrl;https://api.waqi.info/feed/geo:${lat};${lon}/?token=5848198a671c35b7c4d0d870c69d1f079b3a0656 uploadData;<Unused> verifySslCert;Yes version;HTTP_2
    TEST_DIALOG_RESPONSE_PREVIEW = Specify test values and send test request, to view test response.
    TEST_DIALOG_RESPONSE_STATUS = Specify test values and send test request, to view test response.
    TRANSFER_TIMEOUT_LENGTH = 90
    USE_COOKIES = No
    VERIFY_SSL_CERTIFICATES = Yes
    -> JSONFormatter_2
    -> JSONFragmenter
JSONFormatter_2
    ERROR_LIST_ATTR = _json_error
    FORMAT_LOOKUP = PRETTY_PRINT
    INDENT_SIZE = 3
    JSON_DOCUMENT = @Value(_response_body)
    OUTPUT_ATTR = _formatted
    OUTPUT_ENCODING = UTF-8
    READ_FROM_FILE = NO
    REMOVE_EMPTY_OBJECTS_AND_ARRAYS_LOOKUP = NO
    REMOVE_EMPTY_STRINGS_LOOKUP = NO
    REMOVE_NULLS_LOOKUP = NO
    FORMAT = Pretty Print
    INDENT_STYLE = 3 spaces
    REMOVE_EMPTY_OBJECTS_AND_ARRAYS = No
    REMOVE_EMPTY_STRINGS = No
    REMOVE_NULLS = No
JSONFragmenter
    EXPLODE_FORMAT = JSON
    EXTRACT_ATTR = Yes
    JSON_ATTR = _response_body
    JSON_QUERY = json[*]
    NEW_ATTRIBUTES = aqi buffer
    READ_FROM_FILE = NO
    RECURSIVE = YES
    REJECT_EMPTY_LISTS = NO
    FRAGMENTS -> Tester
Tester
    BOOL_OP = OR
    TEST_CLAUSE = TEST aqi ATTRIBUTE_IS_MISSING ""
    TEST_MODE = TEST
    FAILED -> VertexCreator
VertexCreator
    MEASURE_TYPE_LOOKUP = CONTINUOUS
    MODE = REPLACE
    REMOVE_ATTRIBUTES = No
    XVAL = @Value(lon)
    YVAL = @Value(lat)
    ZVAL = @Value(aqi)
    MEASURE_TYPE = Continuous
    MODE_NAME = Replace with Point
    -> NumericRasterizer
NumericRasterizer
    ANTI_ALIASING = No
    BACKGROUND_VALUE = 0
    COLUMNS = @Value(aqi)
    FILL_WITH_NODATA = Yes
    INTERPRETATION_TYPE_LOOKUP = REAL64
    ROWCOL_OR_CELLSIZE = RowsColumns
    ROWS = @Value(aqi)
    SPECIFY_GROUND_EXTENTS = Use input data ground extents
    TOLERANCE = 0.5
    INTERPRETATION_TYPE = Real64
    RASTER -> RasterSelector
RasterSelector
    BAND_LIST = ALL:ALL
    SELECTION_MODE_LOOKUP = USER
    SELECTION_MODE = Band and Palette List
